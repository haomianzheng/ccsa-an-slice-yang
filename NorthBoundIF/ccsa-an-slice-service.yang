module ccsa-an-slice-service {
  namespace "urn:ccsa:yang:ccsa-an-slice-service";
  prefix an-service;

  import ietf-inet-types {
    prefix inet;
  }

  import ietf-yang-types {
    prefix yang;
  }

  import bbf-dot1q-types {
    prefix bbf-dot1qt;
  }

  import ccsa-an-slice-pub-type {
    prefix an-slice-type;
  }

  organization
    "CCSA TC6WG2. ";

  description
    "The model is defined for Access Network service slicing.";

  revision 2023-10-08{
    description
      "Submit for Final Version.";
  }

  identity isolation-type {
    description
      "Base identity from which specific isolation types are derived.";
  }

  identity physical-isolation {
    base isolation-type;
    description
      "Physical isolation.";
  }

  identity logical-isolation {
    base isolation-type;
    description
      "Logical isolation.";
  }

  typedef ip-address-or-prefix {
    type union {
      type inet:ip-address;
      type inet:ip-prefix;
    }

    description
      "The ip-address-or-prefix type represent either an IP address or an IP prefix.";
  }

  grouping traffic-grouping {
    description
      "Network traffic.";

    leaf fixed-bandwidth {
      type uint64;
      units bit/s;
      description
        "Link capacity that is allocated to the given traffic flow.";
    }

    leaf max-latency {
      type uint32;
      units us;
      description
        "Maximum latency in microseconds.";
    }

    leaf max-jitter {
      type uint32;
      units us;
      description
        "The variation in packet delay is called jitter.
         Packet delay variation (PDV) is measured by the difference
         in the one-way delay between sequential packets in a flow.
         jitter quantified in units of microseconds.";
    }

    leaf max-loss {
      type decimal64 {
        fraction-digits 6;
      }
      units %;
      description
        "Packet loss as a percentage of the total traffic sent
         over a configurable interval. ";
    }
  }

  grouping auth-grouping {
    description
      "Authentication.";

    leaf user-name {
      type an-slice-type:username;

      description
        "Authentication user name.";
    }

    leaf password {
      type an-slice-type:password;

      description
        "Authentication password.";
    }
  }

  grouping sla-grouping {
    description
      "Service Level Agreement (SLA) of the APAN slicing.";

    container upstream {
      description
        "Configure upstream Service Level Agreement (SLA).";

      uses traffic-grouping;
    }

    container downstream {
      description
        "Configure downstream Service Level Agreement (SLA).";

      uses traffic-grouping;
    }

  }

  grouping vlan-grouping {
    description
      "VLAN.";

    leaf outer-vlan {
      type bbf-dot1qt:vlan-id;
      description
        "Outer VLAN.";
    }

    leaf inner-vlan {
      type bbf-dot1qt:vlan-id;
      description
        "Inner VLAN.";
    }
  }

  container slice-service {
    description
      "For the management of service slice instances.";

    container sla-templates {
      description
        "List of Service Level Agreement (SLA) templates.";

      list sla-template { 
        key "template-name";
        description
          "Configure Service Level Agreement (SLA) template.";

        leaf template-name {
          type string;
          description
            "Service Level Agreement (SLA) templates name.";
        }

        uses sla-grouping;
      }
    }

    container ns-templates {
      description
        "List of Network Slicing Templates (NST).";

      list ns-template {
        key "name";
        description
          "Configure Network Slicing Templates (NST).";

        leaf name {
          type string;

          description
            "Network slicing template name.";
        }

        leaf sla-template-name {
          type leafref {
            path "/slice-service/sla-templates/sla-template/template-name";
          }

          description
            "Bind a Service Level Agreement (SLA) Template by name.";
        }

        leaf isolation-type {
          type identityref {
            base isolation-type;
          }
          description
            "The service isolation level.";
        }

        list app-info {
            key "app-type app-name";
            leaf app-type{
              type string;
              description
                "The APP type. For Example: APP-ALL/APP-OTT-VIDEO/APP-GAME/APP-EDUCATION/APP-OFFICE/APP-SELF-OPER-VIDEO/APP-SHORT-VIDEO/...  ";     
            }  
            leaf app-name{
              type string;
              description
                "The APP name.  For Example:  TENCENT-VIDEO/VIP-KID/HONOR-OF-KINGS/...";     
            }                 
        }
      }
    }

    container ns-instances {
      description
        "List of Network Service Slicing Instance (NSI).";

      list ns-instance {
        key "nsi-id";
        description
          "Configure network slice instance.";
        
        leaf nsi-id {
          type yang:uuid;
        }

        leaf nst-name {
          type leafref {
            path "/slice-service/ns-templates/ns-template/name";
          }

          description
            "Network slice template name.";
        }

        container olts {
          description
            "List of olt.";

          list olt {
            key "olt-res-id";
            description
            "Configure olt for network slicing instance.";

            leaf olt-res-id {
              type yang:uuid;
              description
                "Olt neid.";
            }

            container nni-ports {
              description
                "List of network point ports.";

              list nni-port {
                key "ltp-slice-res-id";
                description
                  "Indicates the unique ID of the ltp slice.";
                uses an-slice-type:ltp-slice-single;
              }
            }

            container uni-ports {
              description
                "List of UNI ports.";
              list uni-port {
               key "ltp-slice-res-id";
               description
                "Indicates the unique ID of the ltp slice.";    
                uses  an-slice-type:ltp-slice-single;
              }
            }
          }
        }

        container onus {
          description
            "List of ont.";

          list onu {
            key "onu-res-id";
            description
               "Configure ont network slicing instance.";

            leaf onu-res-id {
              type string {
                pattern '[0-9a-z]{8}-[0-9a-z]{4}-[0-9a-z]{4}-[0-9a-z]{4}-[0-9a-z]{12}';
              }
              description
                "Indicates the unique ID of the ONU. The type is UUID..";
         
            }

            leaf wan-auth-type{
                type  an-slice-type:wan-auth-type;    
                description
                    "The auth type for the WAN port, include IPoE/PPPoE/... .";        
            }
          }
        }
      }
    }
  }
}
