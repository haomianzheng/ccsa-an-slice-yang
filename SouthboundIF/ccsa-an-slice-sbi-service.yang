module ccsa-an-slice-sbi-service {
  namespace "urn:ccsa:yang:ccsa-an-slice-sbi-service";
  prefix an-slice-sbi-service;

  import ietf-interfaces {
    prefix if;
  }
  import iana-if-type {
    prefix ianaift;
  }
  import ccsa-an-slice-sbi-vlan {
    prefix an-slice-vlan;
  }
  import ccsa-an-slice-sbi-resource {
    prefix an-slice-sbi-res;
  }

  organization
    "CCSA.";
  contact
    "CCSA";
  description
    "Applicable for device configuration, of network service slices.";

  revision 2023-11-01 {
    description
      "Submit for Final Version";
  }

  typedef nsi-service-type {
    type enumeration {
      enum any {
        value 0;
        description
          "Indicates that the slice service type is not limited.";
      }
      enum multicast {
        value 1;
        description
          "Indicates the multicast duplication mode to multicast.
           The access device duplicates only one multicast packet to each PON port after receiving a multicast packet.
           The Layer 2 device then duplicates the multicast packet to the multicast users.
           The PON ports support the connection admission control (CAC) function.";
      }
    }
    description
      "Indicates the slice service type.";
  }

  grouping slice-bandwidth {
    description
      "Indicates the bandwidth and convergence ratio of a slice.";
    leaf bandwidth {
      type uint64;
      units "bits/second";
      mandatory true;
      description
        "Indicates the bandwidth allocated to the interface.";
    }
    leaf convergence-ratio {
      type decimal64 {
        fraction-digits 1;
        range "1.0..5.0";
      }
      default "1.0";
      description
        "Configure the bandwidth convergence ratio of the interface.";
    }
  }

  grouping slice-instance-attr {
    description
      "Indicates a network slice instance attribute.";
    leaf slice-name {
      type string;
      description
        "Indicates the name of a slice instance. Names with only one or more space characters are not supported.";
    }
    leaf priority {
      type uint8 {
        range "1..7";
      }
      mandatory true;
      description
        "Indicates the slice priority. 7 indicates the highest priority and 1 indicates the lowest priority.
         0 indicates for bronze slices without device support, so 0 is not allowed here.  ";
    }
    leaf queue-buffer {
      type uint8 {
        range "1..16";
      }
      description
        "Configure a queue cache level for a network slice.";
    }
    leaf service-type {
      type nsi-service-type;
      default "any";
      description
        "Indicates the slice service type.";
    }
  }

  grouping slice-instance-vlan {
    description
      "Indicates a network slice instance VLAN.";
    container vlans {
      description
        "List of VLANs in a network slice instance.";
      list network-vlan {
        key "vlan-id";
        description
          "Configure network VLAN to a network slice, consistent with S-VLAN ID.";
        leaf vlan-id {
          type an-slice-vlan:l2-forwarder;
          description
            "Configure a VLAN to a network slice.
              VLAN 1 and reserved VLANs cannot be added to network slices.
              After a port VLAN or service flow is added to a VLAN, the VLAN cannot be added to a network slice.
              A slice can be added to a maximum of 32 VLANs.";
        }
      }
      list user-vlan {
        key "vlan-id";
        description
          "Configure user VLAN to a network slice.";
        leaf vlan-id {
          type an-slice-vlan:l2-forwarder;
          description
            "Configure a VLAN to a network slice.
              VLAN 1 and reserved VLANs cannot be added to network slices.
              After a port VLAN or service flow is added to a VLAN, the VLAN cannot be added to a network slice.
              A slice can be added to a maximum of 32 VLANs.";
        }
      }
    }
  }

  grouping slice-instance-vni {
    description
      "Indicates a network slice instance VNI.";
    container vxlans {
      description
        "List of VXLANs in a network slice instance.";
      list vxlan {
        key "vni-id";
        description
          "Configure vxlan to a network slice.";
        leaf vni-id {
          type uint32 {
            range "1..16777215";
          }
          description
            "Configure VXLAN to a network slice. A maximum of 32 VXLANs can be added to a slice.";
        }
      }
    }
  }

  grouping slice-instance-port {
    description
      "Indicates a network slice instance port or channel.";
    container ports {
      description
        "List of ports in a network slice instance.";
      list port {
        key "ifname";
        description
          "Configure ethernetCsmacd ports, epon ports or gpon ports or vports to a network slice.";
        leaf ifname {
          type if:interface-ref;
          must "/if:interfaces/if:interface[if:name = current()]/if:type='ianaift:ethernetCsmacd' or
                /if:interfaces/if:interface[if:name = current()]/if:type='ianaift:gpon' or
                /if:interfaces/if:interface[if:name = current()]/if:type='ianaift:aluEpon' or
                /if:interfaces/if:interface[if:name = current()]/if:type='bbf-xponift:ani'  or
                /if:interfaces/if:interface[if:name = current()]/if:type='bbf-xponift:v-ani' or
                /if:interfaces/if:interface[if:name = current()]/if:type='bbf-xponift:channel-pair' or
                /if:interfaces/if:interface[if:name = current()]/if:type='bbf-xponift:channel-termination'";
          description
            "Name of interface.";
        }
        uses slice-bandwidth;
      }
    }
  }

  grouping slice-instance {
    description
      "Indicates a network slice instance.";
    container slice-instances {
      description
        "List of Slice Instances.";
      list slice-instance {
        key "slice-name";
        description
          "Configure a slice instance.";
        uses slice-instance-attr;
        uses slice-instance-vlan;
        uses slice-instance-vni;
        uses slice-instance-port;
      }
    }
  }

  augment "/an-slice-sbi-res:slice-an/an-slice-sbi-res:dedicated-networks/an-slice-sbi-res:dedicated-network" {
    description
      "Indicates a network slice instance can be configured under a dedicated network.";
    uses slice-instance;
  }

  container bb-nsi {
    description
      "Indicates a slice instance configured without a dedicated network.";
    uses slice-instance;
  }
}
