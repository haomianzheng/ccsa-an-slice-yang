module ccsa-an-slice-sbi-vlan {
  namespace "urn:ccsa:yang:ccsa-an-slice-sbi-vlan";
  prefix an-slice-vlan;

  import bbf-dot1q-types {
    prefix bbf-dot1qt;
  }

  organization
    "CCSA.";
  description
    "This module contains a collection of YANG definitions for
     managing vlans.";

  revision 2023-11-01 {
    description
      "Submit for final version.";
  }

  /*
   * Typedefs
   */

  typedef vlan-forwarder {
    type string {
      pattern 'forwarder\\.(\\S+)\\.(\\d{1,4})';
    }
    description
      "Indicates the VLAN forwarding domain. For example 'forwader.slice1.100' means the VLAN=100 in slice1.";
  }

  typedef l2-forwarder {
    type union {
      type bbf-dot1qt:vlan-id;
      type vlan-forwarder;
    }
    description
      "Indicates the Layer 2 VLAN forwarding domain.";
  }

}
